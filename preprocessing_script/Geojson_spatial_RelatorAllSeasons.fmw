FME workspace Geojson_spatial_RelatorAllSeasons.fmw

Parameters:
- SourceDataset_WFS = https://ons-inspire.esriuk.com/arcgis/services/Eurostat_Boundaries/NUTS_Level_2_January_2018_Boundaries/MapServer/WFSServer?request=GetCapabilities&service=WFS   # Source WFS (Web Feature Service) URL
- DestDataset_GEOJSON = $(FME_MF_DIR)counties\AllSeasons.json   # Destination GeoJSON File
- SourceDataset_GEOJSON = $(FME_MF_DIR)HomeWinsAllSeasons.geojson   # Source GeoJSON File or URL

Readers:
- WFS_1: WFS from $(SourceDataset_WFS)
- GEOJSON_1: GEOJSON from $(SourceDataset_GEOJSON)

Writers:
- GEOJSON_2: GEOJSON to $(DestDataset_GEOJSON)

NUTS_Level_2__January_2018__Full_Clipped_Boundaries_in_the_United_Kingdom (reader WFS_1)
    attributes: gml_parent_id xml_buffer, gml_parent_property xml_buffer, gml_id xml_buffer, FID xml_int32, NUTS218CD xml_char(4), NUTS218NM xml_char(48), BNG_E xml_int32, BNG_N xml_int32, LONG xml_real64, LAT xml_real64, shape xml_geometry, st_area_shape_ xml_real64, st_length_shape_ xml_real64
    -> Reprojector
Reprojector
    DEST = EPSG:4326
    INTERPOLATION_TYPE_NAME = Nearest Neighbor
    RASTER_CELL_SIZE = Preserve Cells
    RASTER_TOLERANCE = 0.0
    SOURCE = Read from feature
    REPROJECTED -> SpatialRelator [Requestor]
HomeWinsAllSeasons (reader GEOJSON_1)
    attributes: HomeTeam int, key string, Team string, FDCOUK string, City string, Stadium string, Capacity int, Latitude float, Longitude float, Country string
    -> Reprojector_2
Reprojector_2
    DEST = EPSG:4326
    INTERPOLATION_TYPE_NAME = Nearest Neighbor
    RASTER_CELL_SIZE = Preserve Cells
    RASTER_TOLERANCE = 0.0
    SOURCE = Read from feature
    REPROJECTED -> SpatialRelator [Supplier]
SpatialRelator
    AGGREGATE_HANDLING = Yes
    CALC_CARD = No
    CURVE_BOUNDARY_RULE_PARAM = Default Rule
    LIST_ATTRS_TO_INCLUDE = Capacity FDCOUK HomeTeam
    LIST_NAME = _relationships
    PREDICATES = CONTAINS TOUCHES WITHIN
    SUCCESS_ATTR = _related_candidates
    -> ListSummer
ListSummer
    RESULT = sumCapacity
    SRC_LIST = _relationships{}.Capacity
    -> ListSummer_2
ListSummer_2
    RESULT = sumHWins
    SRC_LIST = _relationships{}.HomeTeam
    -> ListConcatenator
ListConcatenator
    DROP_EMPTY_PARTS = No
    LIST_ATTR = _relationships{}.FDCOUK
    SEP = ;
    VAL_ATTR = TeamsNames
    -> AttributeRemover
AttributeRemover
    LIST_ATTRS = _relationships{} _relationships{}.Capacity _relationships{}.FDCOUK _relationships{}.HomeTeam _relationships{}.de9im _relationships{}.pass{}
    REMOVE_ATTRS = st_area_shape_,_related_candidates,st_length_shape_
    -> Tester
Note: only having wins counties
Tester
    BOOL_OP = OR
    COMPOSITE_TEST = 1
    TEST_CLAUSE = TEST @Value(sumHWins) != 0
    TEST_MODE = TEST
    PASSED -> nuts2_countiesUK (writer GEOJSON_2)
nuts2_countiesUK (writer GEOJSON_2)
    attributes: gml_parent_id string, gml_parent_property string, gml_id string, FID int, NUTS218CD string, NUTS218NM string, BNG_E int, BNG_N int, LONG float, LAT float, shape string, sumCapacity int, sumHWins int, TeamsNames string
