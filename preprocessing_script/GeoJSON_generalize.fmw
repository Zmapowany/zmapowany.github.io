FME workspace GeoJSON_generalize.fmw

Parameters:
- SourceDataset_GEOJSON = C:\CartoPush\GitHubPage\data\AllSeasons.json   # Source GeoJSON File or URL
- DestDataset_GEOJSON = C:\CartoPush\GitHubPage\data\AllSeasonsGen2.json   # Destination GeoJSON File

Readers:
- GEOJSON_1: GEOJSON from $(SourceDataset_GEOJSON)

Writers:
- GEOJSON_2: GEOJSON to $(DestDataset_GEOJSON)

nuts2_countiesUK (reader GEOJSON_1)
    attributes: gml_parent_property string, gml_id string, FID int, NUTS218CD string, NUTS218NM string, BNG_E int, BNG_N int, LONG float, LAT float, sumCapacity int, sumHWins int, TeamsNames string
    -> Reprojector
Reprojector
    DEST = EPSG:3857
    INTERPOLATION_TYPE_NAME = Nearest Neighbor
    RASTER_CELL_SIZE = Preserve Cells
    RASTER_TOLERANCE = 0.0
    SOURCE = Read from feature
    REPROJECTED -> Generalizer
    REPROJECTED -> Reprojector_Reprojected
Generalizer
    ALG_TEXT = Douglas (Generalize)
    CLEANING_TOLERANCE = Automatic
    PRESERVE = Yes
    PRESERVE_PATHS = No
    TOLERANCE = 200
    -> Deaggregator
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Bufferer
Bufferer
    ANGLE = 22.5
    CAP_STYLE = Arc
    CORNER_STYLE = Arc
    MODE = AREA
    OFFSET = 500
    OFFSET_UNITS = METERS
    PRECISION = APPROX
    BUFFERED -> Dissolver
Dissolver
    ACCUM_INPUT_ATTRS = Use Attributes From One Feature
    CLEANING_TOLERANCE = Automatic
    CONNECT_Z_MODE = First Wins
    DEAGGREGATE_INPUT = Yes
    GROUP_BY = gml_id
    AREA -> AreaCalculator
Note: no donuts
DonutHoleExtractor
    DEAGGREGATE_INPUT = Yes
    OUTERSHELL -> AttributeRemover
AttributeRemover
    LIST_ATTRS = _hierarchy_child_id_list{}
    REMOVE_ATTRS = _area,_count,_geometry_name,_hierarchy_child_id_list{0},_hierarchy_id,_hierarchy_parent_id,_part_number,areaKM
    -> Bufferer_2
Bufferer_2
    ANGLE = 22.5
    CAP_STYLE = Arc
    CORNER_STYLE = Arc
    MODE = AREA
    OFFSET = -500
    OFFSET_UNITS = NONE
    PRECISION = APPROX
    BUFFERED -> AreaOnAreaOverlayer [AREA]
AreaOnAreaOverlayer
    ACCUM_ATTRS_NAME = Use Attributes From One Feature
    CLEANING_TOLERANCE = Automatic
    CONNECT_Z_MODE = First Wins
    DEAGGREGATE_INPUT = Yes
    OVC_ATTR = _overlaps
    AREA -> TestFilter
TestFilter
    DEFAULT_VALUE = <UNFILTERED>
    TEST_LIST = "BOOL_OP,OR,COMPOSITE_TEST,""""""1"""""",TEST_CLAUSE,TEST @Value(_overlaps) > 1",overlaps
    <UNFILTERED> -> AreaCalculator_2
    overlaps -> Aggregator
Aggregator
    ACCUM_ATTRS_NAME = Use Attributes From One Feature
    AGGREGATE_TYPE = Homogeneous Collection (If Possible)
    GROUP_BY = gml_id
    MODE = Geometry - Assemble One Level
    SEP = ,
    AGGREGATE -> Dissolver_2
Dissolver_2
    ACCUM_INPUT_ATTRS = Use Attributes From One Feature
    CLEANING_TOLERANCE = Automatic
    CONNECT_Z_MODE = First Wins
    DEAGGREGATE_INPUT = Yes
    GROUP_BY = gml_id
    AREA -> AreaOnAreaOverlayer_2 [AREA]
AreaOnAreaOverlayer_2
    ACCUM_ATTRS_NAME = Use Attributes From One Feature
    CLEANING_TOLERANCE = Automatic
    CONNECT_Z_MODE = First Wins
    DEAGGREGATE_INPUT = Yes
    OVC_ATTR = _overlaps
    AREA -> GeometryValidator
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]FME_CONTROLLER_QUERY_FILE]transformers/dependencies/geometryvalidator/SELF_INTERSECTING.fme OGC_SIMPLE_CHECK
    SUMMARY = Detailed
    PASSED -> Generalizer_2
    REPAIRED -> Generalizer_2
Generalizer_2
    ALG_TEXT = Douglas (Generalize)
    CLEANING_TOLERANCE = Automatic
    PRESERVE = Yes
    PRESERVE_PATHS = No
    TOLERANCE = 200
    -> Generalizer_3
    -> nuts2_countiesUK (writer GEOJSON_2) [off]
Generalizer_3
    ALG_TEXT = Douglas (Generalize)
    CLEANING_TOLERANCE = Automatic
    PRESERVE = Yes
    PRESERVE_PATHS = No
    TOLERANCE = 2000
    -> nuts2_countiesUK (writer GEOJSON_2)
nuts2_countiesUK (writer GEOJSON_2)
    attributes: gml_parent_property string, gml_id string, FID int, NUTS218CD string, NUTS218NM string, BNG_E int, BNG_N int, LONG float, LAT float, sumCapacity int, sumHWins int, TeamsNames string
Reprojector_Reprojected: Inspector

Bookmark: filter out small polygons
AreaCalculator
    AREA_ATTR = _area
    AREA_TYPE = Plane Area
    MULT = 1
    -> ExpressionEvaluator
ExpressionEvaluator
    ACTION = Create New Attribute
    EXPRESSION = @div(@Value(_area),1000)
    VAL_ATTR = areaKM
    -> AttributeRounder
AttributeRounder
    PLACES = 0
    ROUND_TYPE = Nearest
    SRC_ATTRS = areaKM
    -> Sorter
Sorter
    GROUP_BY = gml_id
    SORT_PARM = areaKM NUMERIC DESCENDING
    SORTED -> Counter
Counter
    CNT_ATTR = _count
    DOMAIN = @Value(gml_id)
    SCOPE = Local
    START = 1
    -> Tester
Tester
    BOOL_OP = OR
    COMPOSITE_TEST = 1
    TEST_CLAUSE = TEST @Value(_count) = 1
    TEST_MODE = TEST
    PASSED -> DonutHoleExtractor

Bookmark: filter out small polygons
AreaCalculator_2
    AREA_ATTR = _area
    AREA_TYPE = Plane Area
    MULT = 1
    -> ExpressionEvaluator_2
ExpressionEvaluator_2
    ACTION = Create New Attribute
    EXPRESSION = @div(@Value(_area),1000)
    VAL_ATTR = areaKM
    -> AttributeRounder_2
AttributeRounder_2
    PLACES = 0
    ROUND_TYPE = Nearest
    SRC_ATTRS = areaKM
    -> Sorter_2
Sorter_2
    GROUP_BY = gml_id
    SORT_PARM = areaKM NUMERIC DESCENDING
    SORTED -> Counter_2
Counter_2
    CNT_ATTR = _count
    DOMAIN = @Value(gml_id)
    SCOPE = Local
    START = 1
    -> Tester_2
Tester_2
    BOOL_OP = OR
    COMPOSITE_TEST = 1
    TEST_CLAUSE = TEST @Value(_count) = 1
    TEST_MODE = TEST
    PASSED -> Aggregator
